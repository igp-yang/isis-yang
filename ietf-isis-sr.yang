module ietf-isis-sr {
  namespace "urn:ietf:params:xml:ns:"
          + "yang:ietf-isis-sr";
  prefix isis-sr;

  
  import ietf-routing {
    prefix "rt";
  }
  
  import ietf-segment-routing {
	prefix "sr";
  }
  
  import ietf-isis {
	prefix "isis";
  }
  
  organization
   "IETF ISIS Working Group";
   
  contact
    "WG List:  &lt;mailto:spring@ietf.org&gt;
    
    Editor:    Stephane Litkowski
          &lt;mailto:stephane.litkowski@orange.com&gt;

        Acee Lindem
          &lt;mailto:acee@cisco.com&gt;
		Yingzhen Qu
		  &lt;mailto:yiqu@cisco.com&gt;
        Pushpasis Sarkar
          &lt;mailto:psarkar@juniper.net&gt;
        Ing-Wher Chen
          &lt;mailto:ing-wher.chen@ericsson.com&gt;
		Jeff Tantsura
		  &lt;mailto:jeff.tantsura@ericsson.com&gt;
		  
    ";
  
  description 
    "The YANG module defines a generic configuration model for 
    Segment routing ISIS extensions common across all of the vendor 
    implementations.";

  revision 2016-03-21 {
   description "
   * Removed routing-instance in path as per 
   core routing model v21
   ";
   reference "";
  }
  revision 2015-09-18 {
   description "no modif";
   reference "";
  }
  revision 2015-07-02 {
	description
	 " 
	 * Add TILFA and rLFA SR
	 * Add container to SRGB
	 ";
	reference "";
  }
  
  revision 2015-05-27 {
    description "
	 * Initialization
	";
	reference "";
  }

  
  /* Identities */
  
  
  /* Features */
  
feature remote-lfa-sr {
	description
	 "Enhance rLFA to use SR path.";
}

feature ti-lfa {
	description
	 "Enhance IPFRR with ti-lfa 
	 support";
}
  
  /* Groupings */
 
grouping adjacency-state {
	description
	 "This group will extend adjacency state.";
	list adjacency-sid {
	  key value;
	  leaf af {
		type identityref {
		  base rt:address-family;
		}
		description
		 "Address-family associated with the 
		 segment ID";
	  }
	  leaf value {
		type uint32;
		description
		 "Value of the Adj-SID.";
	  }
	  leaf weight {
		type uint8;
		description
		 "Weight associated with
		 the adjacency SID.";
	  }
	  leaf protection-requested {
		type boolean;
		description
		 "Describe if the adjacency SID
		 must be protected.";
	  }
	  description
	   "List of adjacency Segment IDs.";
	}
}

grouping prefix-segment-id {
    description
     "This group defines segment routing extensions
     for prefixes.";
    
	list sid-list {
	  key value;
	  
      leaf flags {
        type bits {
          bit readvertisment {
            position 7;
            description
             "If set, then the prefix to
            which this Prefix-SID is attached, 
            has been propagated by the
            router either from another level
            or from redistribution.";
          }

          bit php {
            position 5;
            description
            "If set, then the penultimate hop MUST NOT
            pop the Prefix-SID before delivering the packet 
            to the node
            that advertised the Prefix-SID.";
          }
          bit explicit-null {
            position 4;
            description
            "If set, any upstream neighbor of
            the Prefix-SID originator MUST replace 
            the Prefix-SID with a
            Prefix-SID having an 
            Explicit-NULL value (0 for IPv4 and 2 for
            IPv6) before forwarding the packet.";
          }
          bit  value {
            position 3;
            description
            "If set, then the Prefix-SID carries a
            value (instead of an index).  
            By default the flag is UNSET.";


          }
          bit  local {
            position 2;
            description
            "If set, then the value/index carried by
            the Prefix-SID has local significance.  
            By default the flag is UNSET.";
          }
        }
        description
         "Describes flags associated with the
         segment ID.";
      }
      
      leaf algorithm {
        type uint8;
        description
         "Algorithm to be used for path computation.";
      }
      leaf value {
        type uint32;
        description
         "Value of the prefix-SID.";
      }
	  description
	   "List of segments.";
    }
  }
  
  grouping adjacency-segment-id {
    description
     "This group defines segment routing extensions
     for adjacencies.";
    
	list sid-list {
	  key value;
	  
      leaf flags {
        type bits {
          bit address-family {
            position 7;
            description
             "If unset, then the Adj-SID refers
            to an adjacency with outgoing IPv4 encapsulation.  
            If set then the Adj-SID refers to an adjacency 
            with outgoing IPv6 encapsulation.";
          }
          bit backup {
            position 6;
            description
             "If set, the Adj-SID refers to an
            adjacency being protected 
            (e.g.: using IPFRR or MPLS-FRR)";
          }
          bit  value {
            position 5;
            description
            "If set, then the SID carries a
            value (instead of an index).  
            By default the flag is SET.";


          }
          bit  local {
            position 4;
            description
            "If set, then the value/index carried by
            the SID has local significance.  
            By default the flag is SET.";
          }
          bit  set {
            position 3;
            description
            "When set, the S-Flag indicates that the
            Adj-SID refers to a set of adjacencies";
          }
        }
        
        description
         "Describes flags associated with the
         segment ID.";
      }
      leaf weight {
        type uint8;
        description
         "The value represents the weight of the Adj-SID
          for the purpose of load balancing.";
      }
      leaf neighbor-id {
        type isis:system-id;
        description
         "Describes the system ID of the neighbor
         associated with the SID value. This is only
         used on LAN adjacencies.";
      }
      leaf value {
        type uint32;
        description
         "Value of the Adj-SID.";
      }
	  description
	   "List of segments.";
    }

  }
  grouping segment-routing-binding-tlv {
  list segment-routing-bindings {
      
      key "fec range";
      
      leaf fec {
        type string;
        description
        "IP (v4 or v6) range to be bound to SIDs.";
      }
      
      leaf range {
        type uint16;
        description
         "Describes number of elements to assign 
         a binding to.";
      }
      
      leaf flags {
        type bits {
          bit address-family {
            position 7;
            description
            "If unset, then the Prefix FEC
            carries an IPv4 Prefix.  
            If set then the Prefix FEC carries an
            IPv6 Prefix.";
          }
          bit mirror {
            position 6;
            description
            "Set if the advertised SID/path
            corresponds to a mirrored context.
            ";
          }
          bit flooding {
            position 5;
            description
             "If the S bit is set(1), 
             the IS-IS Router CAPABILITY TLV
            MUST be flooded across the entire routing domain.  
            If the S bit is
            not set(0), the TLV MUST NOT be leaked between levels.  
            This bit MUST NOT be altered during the TLV leaking.";
          }
          bit down {
            position 4;
            description
            "When the IS-IS Router CAPABILITY TLV is 
            leaked from level-2 to level-1, the D bit 
            MUST be set.  Otherwise, this bit MUST
            be clear.  IS-IS Router capability TLVs 
            with the D bit set MUST NOT
            be leaked from level-1 to level-2.  
            This is to prevent TLV looping.
            ";
          }
          bit attached {
            position 3;
            description
            "The originator of the SID/Label Binding
            TLV MAY set the A bit in order to signal
            that the prefixes and
            SIDs advertised in the SID/Label Binding
            TLV are directly
            connected to their originators.
            ";
          }
          
        }
        description
           "Flags of the binding.";
      }
      
      leaf weight {
        type uint8;
        description
         "Weight of the path for loadbalancing purpose.";
      }
      
      list binding {
        container prefix-sid {
          uses prefix-segment-id;
          description
           "Binding prefix SID to the range.";
        }
        leaf ero-metric {
          type uint32;
          description
           "Cost of ERO path.";
        }
        container ero {
          leaf address-family {
            type identityref {
              base rt:address-family;
            }
            description
             "Address-family.";
          }
          
          leaf loose {
            type boolean;
            description
             "Set to true, 
             if hop is a loose hop.";
          }
          leaf address {
            type string;
            description
            "IP address of a node on the
            path.";
          }
          
          description
           "Binding ERO path to the range.";
        }
        container backup-ero {
          leaf address-family {
            type identityref {
              base rt:address-family;
            }
            description
             "Address-family.";
          }
          
          leaf loose {
            type boolean;
            description
             "Set to true, 
             if hop is a loose hop.";
          }
          leaf address {
            type string;
            description
            "IP address of a node on the
            path.";
          }
          
          description
           "Binding backup ERO path to the range.";
        }
        container unnumbered-interface-id-ero {
          leaf router-id {
            type string;
            description
             "Router ID of the node owning the interface.";
          }
          leaf interface-id {
            type uint32;
            description
            "Interface ID on which the path is built.";
          }
          description
           "Binding a path over unnumbered interface.";
        }
        container backup-unnumbered-interface-id-ero {
          leaf router-id {
            type string;
            description
             "Router ID of the node owning the interface.";
          }
          leaf interface-id {
            type uint32;
            description
            "Interface ID on which the path is built.";
          }
          description
           "Binding a backup path over unnumbered interface.";
        }
        description
         "Bindings associated with the range.";
      }
      
      description 
       "This container describes list of SID/Label
       bindings.
       ISIS reference is TLV 149.";     
    }
	description
	 "Defines binding TLV for database.";
	 
  }
  /* Cfg */
    
  augment "/rt:routing/" +
        "rt:routing-protocols/rt:routing-protocol"+
        "/isis:isis" {
    when "rt:type = 'isis:isis'" {
      description
      "This augment ISIS routing protocol when used";
    }
    description
     "This augments ISIS protocol configuration
      with segment routing.";
      
    uses sr:controlplane-cfg;
	container protocol-srgb {
         if-feature sr:protocol-srgb;
         uses sr:srgb-cfg;
         description
           "Per-protocol SRGB.";
       }

  }
   
   
   augment "/rt:routing/" +
        "rt:routing-protocols/rt:routing-protocol"+
        "/isis:isis/isis:interfaces/isis:interface" {
    when "rt:type = 'isis:isis'" {
      description
      "This augment ISIS routing protocol when used";
    }
    description
     "This augments ISIS protocol configuration
      with segment routing.";
      
    uses sr:igp-interface-cfg;
  }
  
   augment "/rt:routing/" +
        "rt:routing-protocols/rt:routing-protocol"+
        "/isis:isis/isis:interfaces/isis:interface"+
		"/isis:fast-reroute" {
    when "rt:type = 'isis:isis'" {
      description
      "This augment ISIS routing protocol when used";
    }
    description
     "This augments ISIS IP FRR with TILFA.";
      
	container ti-lfa {
		if-feature ti-lfa;
		leaf enable {
			type boolean;
			description
			 "Enables TI-LFA computation.";
		}
		description
		 "TILFA configuration.";
	}

  }
  
  augment "/rt:routing/" +
        "rt:routing-protocols/rt:routing-protocol"+
        "/isis:isis/isis:interfaces/isis:interface"+
		"/isis:fast-reroute/isis:lfa/isis:remote-lfa" {
    when "rt:type = 'isis:isis'" {
      description
      "This augment ISIS routing protocol when used";
    }
    description
     "This augments ISIS remoteLFA config with
	 use of segment-routing path.";
      
	leaf use-segment-routing-path {
		if-feature remote-lfa-sr;
		type boolean;
		description
		 "force remote LFA to use segment routing
		 path instead of LDP path.";
	}

  }
  
  
  
  /* Operational states */
  
  augment "/rt:routing-state/" +
        "rt:routing-protocols/rt:routing-protocol"+
        "/isis:isis" {
    when "rt:type = 'isis:isis'" {
      description
      "This augment ISIS routing protocol when used";
    }
    description
     "This augments ISIS protocol configuration
      with segment routing.";
      
    uses sr:controlplane-cfg;
	container protocol-srgb {
         if-feature sr:protocol-srgb;
         uses sr:srgb-cfg;
         description
           "Per-protocol SRGB.";
       }

  }
   
   augment "/rt:routing-state/" +
        "rt:routing-protocols/rt:routing-protocol"+
        "/isis:isis/isis:interfaces/isis:interface" {
    when "rt:type = 'isis:isis'" {
      description
      "This augment ISIS routing protocol when used";
    }
    description
     "This augments ISIS protocol configuration
      with segment routing.";
      
    uses sr:igp-interface-cfg;
  }
  
  augment "/rt:routing-state/" +
        "rt:routing-protocols/rt:routing-protocol"+
        "/isis:isis/isis:interfaces/isis:interface" +
		"/isis:adjacencies/isis:adjacency" {
    when "rt:type = 'isis:isis'" {
      description
      "This augment ISIS routing protocol when used";
    }
    description
     "This augments ISIS protocol configuration
      with segment routing.";
      
	
    uses adjacency-state;
  }
  
  augment "/rt:routing-state/" +
        "rt:routing-protocols/rt:routing-protocol"+
        "/isis:isis/isis:database/isis:level-db/isis:lsp"+
		"/isis:extended-is-neighbor/isis:neighbor" {
	description
	 "This augments ISIS protocol LSDB neighbor.";
	uses adjacency-segment-id;
  
  }
  augment "/rt:routing-state/" +
        "rt:routing-protocols/rt:routing-protocol"+
        "/isis:isis/isis:database/isis:level-db/isis:lsp"+
		"/isis:mt-is-neighbor/isis:neighbor" {
		description
	 "This augments ISIS protocol LSDB neighbor.";
	uses adjacency-segment-id;
  
  }
  augment "/rt:routing-state/" +
        "rt:routing-protocols/rt:routing-protocol"+
        "/isis:isis/isis:database/isis:level-db/isis:lsp"+
		"/isis:extended-ipv4-reachability/isis:prefixes" {
		description
	 "This augments ISIS protocol LSDB prefix.";
	uses prefix-segment-id;
  
  }
  augment "/rt:routing-state/" +
        "rt:routing-protocols/rt:routing-protocol"+
        "/isis:isis/isis:database/isis:level-db/isis:lsp"+
		"/isis:mt-extended-ipv4-reachability/isis:prefixes" {
		description
	 "This augments ISIS protocol LSDB prefix.";
	uses prefix-segment-id;
  
  }
  augment "/rt:routing-state/" +
        "rt:routing-protocols/rt:routing-protocol"+
        "/isis:isis/isis:database/isis:level-db/isis:lsp"+
		"/isis:ipv6-reachability/isis:prefixes" {
		description
	 "This augments ISIS protocol LSDB prefix.";
	uses prefix-segment-id;
  
  }
  augment "/rt:routing-state/" +
        "rt:routing-protocols/rt:routing-protocol"+
        "/isis:isis/isis:database/isis:level-db/isis:lsp"+
		"/isis:mt-ipv6-reachability/isis:prefixes" {
		description
	 "This augments ISIS protocol LSDB prefix.";
	uses prefix-segment-id;
  
  }
  augment "/rt:routing-state/" +
        "rt:routing-protocols/rt:routing-protocol"+
        "/isis:isis/isis:database/isis:level-db/isis:lsp" {
		description
	 "This augments ISIS protocol LSDB.";
	uses segment-routing-binding-tlv;
  
  }
  
  
  /* Notifications */
  
 
}
